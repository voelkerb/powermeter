string SamacSysLogo;
string HTMLPane = "";
string SearchQuery = "Enter keyword or manufacturer part number.";
string HomePage (){
     string homepage;
     SamacSysLogo  = "http://componentsearchengine.com/ExtRef/ulp/SamacSys_Logo_2017_255x53.png";
     homepage = "http://componentsearchengine.com/ExtRef/ulp/ulp.htm";
     if( netget( homepage, homepage) >= 0 ){
          return homepage; }
     else {
          // Failed to connect to server
          return "Problem connecting to SamacSys. Please check your internet connection.";
          }
  }
  
int IsWindows() {
  //Returns 1, if EAGLE Is running under Windows (0 for Linux/Mac)
  if ((strsub(argv[0], 0, 1) == "/") && (strsub(argv[0], 0, 2) != "//"))
    return 0;

  return 1;
}  //end sub

int IsMac(){
  if( (strsub( OS_SIGNATURE, 0, 3 ) == "Mac") ||  (strsub( OS_SIGNATURE, 0, 3 ) == "MAC") )
    return 1;

  return 0;}

void LaunchBrowser( string url ){
  string launchCmd = "";
  if( IsWindows() ){
    launchCmd = "explorer \"" + url + "\"";
    }
  else if( IsMac() ){
    launchCmd = "open " + url;
    }
  else{
    //assume all others linux
    //if you are on linux then change this line if the buttons dont work
    launchCmd = "xdg-open " + url;
    }

  //run system command
  system( launchCmd );
  }  //end launch browser




  
void DoSearch(string query)
{
	LaunchBrowser("https://eagle.componentsearchengine.com/search.html?searchString=" + query);
} 
 
string content = HomePage ();
HTMLPane = "<font size=\"4\"> \
       <table width=\100%\"  style=\"font-family:Open Sans;\" align=center> \
       <tr> \
      <td width=\"100%\" style=\"padding-bottom:20px;font:36px;\"> \
       <center><a href=\"https://eagle.componentsearchengine.com\"><img src=\"" + SamacSysLogo + "\"></a></center></td>\
       </tr>"
	   + content +
       "</table> \
       </font>";
int Result = dlgDialog("SamacSys - The leaders in FREE Component Library Content") {

dlgVBoxLayout {
  dlgHBoxLayout dlgSpacing(600);
  dlgHBoxLayout {
  dlgTextView(HTMLPane);
  dlgVBoxLayout dlgSpacing(360);
  }
}
 
dlgHBoxLayout {
       dlgStringEdit( SearchQuery );
       dlgPushButton("+Search"){
	   DoSearch(SearchQuery);}
}  //end box layout
 
 //buttons to submit and exit
dlgHBoxLayout{
dlgHBoxLayout dlgSpacing(610);
     dlgPushButton( "Close" ) dlgReject();
}  //end box layout
};
